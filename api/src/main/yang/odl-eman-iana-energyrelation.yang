module odl-eman-iana-energyrelation {

  /*** NAMESPACE / PREFIX DEFINITION ***/
  namespace "urn:opendaylight:params:xml:ns:yang:eman:iana:energyrelation";
  prefix "iana-energy";

  /*** LINKAGE (IMPORTS / INCLUDES) ***/

  /*** META INFORMATION ***/
  organization
   "IANA";

  contact
   "Internet Assigned Numbers Authority
    Postal: ICANN
    12025 Waterfront Dr., Suite 300
    Los Angeles, CA 90094
    United States
    Tel: +1-310-301-5800
    EMail: iana@iana.org";

  description
   "Copyright (c) 2015 IETF Trust and the persons identified as
    authors of the code.  All rights reserved.

    Redistribution and use in source and binary forms, with or
    without modification, is permitted pursuant to, and subject
    to the license terms contained in, the Simplified BSD
    License set forth in Section 4.c of the IETF Trust's Legal
    Provisions Relating to IETF Documents
    (http://trustee.ietf.org/license-info).

    This MIB module defines a TEXTUAL-CONVENTION that
    describes the relationships between Energy Objects.

    The initial version of this MIB module was published in
    RFC 7461; for full legal notices see the RFC itself.";

  revision "2015-02-09" {
    description
     "Initial version of this MIB as published in
      RFC 7461.";
  }

  /*** TYPE DEFINITIONS ***/
  typedef IANAEnergyRelationship {
    type enumeration {
      enum poweredBy    { value 1; }
      enum powering     { value 2; }
      enum meteredBy    { value 3; }
      enum metering     { value 4; }
      enum aggregatedBy { value 5; }
      enum aggregating  { value 6; }
    }
    description
     "An enumerated value specifying the type of
      relationship between an Energy Object A, on
      which the relationship is specified, with the
      Energy Object B, identified by the UUID.

      The enumeration 'poweredBy' is applicable if
      Energy Object A is poweredBy Energy Object B.

      The enumeration 'powering' is applicable if
      Energy Object A is powering Energy Object B.

      The enumeration 'meteredBy' is applicable if
      Energy Object A is meteredBy Energy Object B.

      The enumeration 'metering' is applicable if
      Energy Object A is metering Energy Object B.

      The enumeration 'aggregatedBy' is applicable if
      Energy Object A is aggregatedBy Energy Object B.

      The enumeration 'aggregating' is applicable if
      Energy Object A is aggregating Energy Object B.";
  }

} /* end of module odl-eman-iana-energyrelation */
