module odl-eman-iana-powersetstate {

  /*** NAMESPACE / PREFIX DEFINITION ***/
  namespace "urn:opendaylight:params:xml:ns:yang:eman:iana:powersetstate";
  prefix "iana-power";

  /*** LINKAGE (IMPORTS / INCLUDES) ***/

  /*** META INFORMATION ***/
  organization
   "IANA";

  contact
   "Internet Assigned Numbers Authority
    Postal: ICANN
    12025 Waterfront Drive, Suite 300
    Los Angeles, CA 90094
    United States
    Tel: +1-310-301 5800
    EMail: iana@iana.org";

  description
   "Copyright (c) 2015 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This MIB module defines the PowerStateSet Textual
    Convention, which specifies the Power State Sets and
    Power State Set Values an Energy Object supports.

    The initial version of this MIB module was published in
    RFC 7460; for full legal notices see the RFC itself.";

  revision "2015-02-09" {
    description
     "Initial version of this MIB module, as published as RFC
      7460.";
  }

  /*** TYPE DEFINITIONS ***/
  typedef PowerStateSet {
    type enumeration {
      enum other                         { value 0; }
      enum unknown                       { value 255; }
      enum ieee1621                      { value 256; }
      enum ieee1621Off                   { value 257; }
      enum ieee1621Sleep                 { value 258; }
      enum ieee1621On                    { value 259; }
      enum dmtf                          { value 512; }
      enum dmtfOn                        { value 513; }
      enum dmtfSleepLight                { value 514; }
      enum dmtfSleepDeep                 { value 515; }
      enum dmtfOffHard                   { value 516; }
      enum dmtfOffSoft                   { value 517; }
      enum dmtfHibernate                 { value 518; }
      enum dmtfPowerOffSoft              { value 519; }
      enum dmtfPowerOffHard              { value 520; }
      enum dmtfMasterBusReset            { value 521; }
      enum dmtfDiagnosticInterrapt       { value 522; }
      enum dmtfOffSoftGraceful           { value 523; }
      enum dmtfOffHardGraceful           { value 524; }
      enum dmtfMasterBusResetGraceful    { value 525; }
      enum dmtfPowerCycleOffSoftGraceful { value 526; }
      enum dmtfPowerCycleHardGraceful    { value 527; }
      enum eman                          { value 1024; }
      enum emanMechOff                   { value 1025; }
      enum emanSoftOff                   { value 1026; }
      enum emanHibernate                 { value 1027; }
      enum emanSleep                     { value 1028; }
      enum emanStandby                   { value 1029; }
      enum emanReady                     { value 1030; }
      enum emanLowMinus                  { value 1031; }
      enum emanLow                       { value 1032; }
      enum emanMediumMinus               { value 1033; }
      enum emanMedium                    { value 1034; }
      enum emanHighMinus                 { value 1035; }
      enum emanHigh                      { value 1036; }
    }
    description
     "IANAPowerState is a textual convention that describes
      Power State Sets and Power State Set Values an Energy
      Object supports.  IANA has created a registry of Power
      State supported by an Energy Object and IANA shall
      administer the list of Power State Sets and Power
      States.

      The Textual Convention assumes that Power States in a
      Power State Set are limited to 255 distinct values.  For
      a Power State Set S, the named number with the value S *
      256 is allocated to indicate the Power State Set.  For a
      Power State X in the Power State Set S, the named number
      with the value S * 256 + X + 1 is allocated to represent
      the Power State.

      Requests for new values should be made to IANA via email
      (iana@iana.org).";
    reference
     "http://www.iana.org/assignments/power-state-sets";
  }

} /* end of module odl-eman-iana-powersetstate */
