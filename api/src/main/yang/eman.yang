module eman {
    yang-version 1;
    namespace "urn:opendaylight:params:xml:ns:yang:eman";
    prefix "eman";

    import ietf-yang-types { prefix yang; }

    organization "Pajarito Technologies LLC";
    contact "Frank Sandoval francisrsandoval@gmail.com";
    description "Defines Data Model of Energy Management module.
        This model is derived from RFC 7326. See IETF Energy Management framework, 
        https://datatracker.ietf.org/wg/eman/charter/
        
        This model is intended to support the IETF eman MIB models. For instance, 
        the powerMeasurement object reflects the EoPowerEntry object found in
        ENERGY-OBJECT-MIB.
        ";

    revision "2017-12-08" {
        description "refactored structure and added complete features of RFC 7326";
    }
    revision "2017-01-05" {
        description "Initial revision of eman model. This is a WORK IN PROGRESS and 
        contains data type definitions and other elements that should be refined";
    }

    feature power-attributes {
        description "Every Energy Object has an optional unique human-readable printable
                        name";
    }
    
    feature eoObject-name {
        description "Every Energy Object has an optional unique human-readable printable
                        name";
    }

    feature eoObject-alternateKey {
        description "An alternate key is provided to allow an Energy Object
                         to be optionally linked with models in different systems";
    }

    feature eoObject-energy {
        description "The Energy Object (Class) contains optional attributes that represent
                        the energy used";
    }

    feature eoObject-demand {
        description "The Energy Object (Class) contains optional attributes that represent
                        demand information over time.";
    }
        
    grouping measurement {
        leaf multiplier {
           type int32 {
                range "-24..24";
           }
           config false;
           description "The magnitude of the Measurement. See RFC 7326";
        }
        leaf caliber {
            type enumeration {
                enum ACTUAL {description "specifies how the Measurement was obtained. See RFC 7326";}
                enum ESTIMATED {description "specifies how the Measurement was obtained. See RFC 7326";}
                enum STATIC {description "specifies how the Measurement was obtained. See RFC 7326";}
            }
           config false;
           description "Specifies how the Measurement was obtained";
        }
        leaf accuracy {
            type uint32 {
                range "0..10000";
            }
            config false;
            description "Specifies the accuracy of the measurement, if applicable, indicating hundreds of percent";
        }
        description "base class for measurement classes";
   }
   
   grouping ACQuality {
        leaf acConfiguration {
            type enumeration {
                enum SNGL {description "single phase";}
                enum DEL {description "three-phase delta";}
                enum WYE {description "three-phase Y";}
            }
           config false;
           description "Describes the physical configuration of alternating current";
        }
        leaf avgVoltage {
            type uint64;
            config false;
            description "The average of the voltage measured over an integral number of AC cycles [IEC61850-7-4] 'Vol'";
        }
         leaf avgCurrent {
            type uint64;
            config false;
            description "The current per phase [IEC61850-7-4] 'Amp'";
        }
        leaf thdCurrent {
            type uint64;
            config false;
            description "A calculated value for the current Total Harmonic Distortion (THD). The method of calculation is not specified [IEC61850-7-4] 'ThdAmp'";
        }
        leaf frequency {
            type uint64;
            config false;
            description "Basic frequency of the AC circuit [IEC61850-7-4] 'Hz'";
        }
        leaf unitMultiplier {
            type uint32;
            config false;
            description "Magnitude of watts for the usage value in this instance";
        }
        leaf accuracy {
            type uint32;
            config false;
            description "Percentage value in 100ths of a percent, representing the presumed accuracy of active, reactive, and apparent power in this instance";
        }
        leaf totalActivePower {
            type uint64;
            config false;
            description "A measured value of the actual power delivered to or consumed by the load [IEC61850-7-4] 'TotW'";
        }
        leaf totalReactivePower {
            type uint64;
            config false;
            description "A measured value of the reactive portion of the apparent power [IEC61850-7-4] 'TotVAr'";
        }
        leaf totalApparentPower {
            type uint64;
            config false;
            description "A measured value of the voltage and current, which determines the apparent power as the vector sum of real and reactive power [IEC61850-7-4] 'TotVA'";
        }
        leaf totalPowerFactor {
            type uint64;
            config false;
            description "A measured value of the ratio of the real power flowing to the load versus the apparent power [IEC61850-7-4] 'TotPF'";
        }
       description "Describes AC Power Attributes for a Measurement";        
   }    
    
    grouping powerMeasurement {
        uses measurement;
        leaf value {
            type uint32;
            config false;
            description "A measurement value of power";
        }
        leaf units {
            type string;
            default "W";
            config false;
            description "The units of measure for the power -- Watts";
        }
        container powerAttribute {
            if-feature power-attributes;
            uses ACQuality;
            description "Describes AC Power Attributes for a Measurement";
        }
        description "The present power measurement of an Energy Objec";
    }
    
    grouping energyMeasurement {
        uses measurement;
        leaf startTime {
            type uint32;
            config false;
            description "A start time of a measurement. TBD. RFC 7326 states type 'time'";
        }
        leaf units {
            type string;
            default "kWh";
            config false;
            description "The units of measure for energy -- kilowatts/hr";
        }
        leaf provided {
            type uint32;
            config false;
            description "A measure of energy provided";
        }
        leaf used {
            type uint32;
            config false;
            description "A measurement value of used";
        }
        leaf produced {
            type uint32;
            config false;
            description "A measurement value of produced";
        }
        leaf stored {
            type uint32;
            config false;
            description "A measurement value of stored";
        }        
        description "The present energy measurement of an Energy Objec";
    }
    
    grouping timeInterval {
        leaf value {
            type uint64;
            config false;
            description "A value of time";
        }
        leaf units  {
            type enumeration {
                enum SECOND {description "A magnitude of time";}
                enum DECISECOND {description "A magnitude of time";}
                enum CENTISECOND {description "A magnitude of time";}
                enum MILLISECOND {description "A magnitude of time";}
                enum MICROSECOND {description "A magnitude of time";}
                enum NANOSECOND {description "A magnitude of time";}
            }
            config false;
            description "A magnitude of time, expressed as seconds with an SI prefix";
        }
        description "an interval of time";
    }

    grouping demandMeasurement {
        uses measurement;
        container intervalLength  {
            uses timeInterval;
            description "The length of time over which to compute average energy";
        }
        leaf intervals {
            type uint64;
            description "The number of intervals that can be measured";
        }
        leaf intervalMode {
            type enumeration {
                enum PERIODIC {description "periodic mode";}
                enum SLIDING {description "sliding mode";}
                enum TOTAL {description "total mode";}
            }
            config false;
            description "The mode of interval measurement";
        }
        container intervalWindow  {
            uses timeInterval;
            description "The duration between the starting time of one sliding window and
                  the next starting time";
        }
        container sampleRate {
            uses timeInterval;
            description "The sampling rate at which to poll power in order to compute demand";
        }
        leaf status {
            type enumeration {
                enum ACTIVE {description "active control";}
                enum INACTIVE {description "inactive control";}
            }
            config false;
            description "A control to start or stop demand  measurement";
        }
        container timedMeasurements {
            list timedMeasurement {
                config false;
                leaf id {type int32;}
                leaf name  {
                    type string;
                    description "A name for this instance";
                }
                leaf startTime {
                    type uint32;
                    config false;
                    description "A start time of a measurement";
                }
                container value {
                    uses powerMeasurement;
                    description "A measurement value";
                }
                container maximum {
                    uses powerMeasurement;
                    description "A maximum value measured since a previous timestamp";
                }
                description "A collection of timedMeasurements to compute demand.
                    RFC 7326 indicates this should support any subclass of measurement, but YANG limits the
                    ability to support polymorphism via the choice statement by requiring that each identifier be unique across cases.
                    We have chosen to constrain value and maximum to type PowerMeasurement";
            }
        }
        description "The present demand measurementfor the Energy Object";
    }
    
    grouping powerStateSet {
        leaf powerStateIdentifier  {
            type uint32;
            config false;
            description "An IANA-assigned value indicatinga Power State Set";
        }
        leaf name  {
            type string;
            config false;
            description "A Power State Set name";
        }
        container powerStates {
            list powerState {
                leaf id {type int32;}
                leaf powerStateIdentifier  {
                    type uint32;
                    config false;
                    description "An IANA-assigned value indicatinga Power State Set";
                }
                leaf name  {
                    type string;
                    config false;
                    description "A Power State Set name";
                }
                leaf cardinality  {
                    type uint32;
                    config false;
                    description "A value indicating an ordering of the Power State";
                }
                container maximumPower {
                    uses powerMeasurement;
                    description "Indicates the maximum power for the Energy Object at this Power State";
                }
                leaf totalTimeInState   {
                    type yang:timeticks;
                    config false;
                    description "Indicates the total time an Energy Object has been in this Power State since
                        the last reset. NOTE: RFC 7362 indicates this is of type Time ";
                }
                leaf entryCount  {
                    type uint64;
                    config false;
                    description "Indicates the number of times the Energy Object has entered or changed to
                         this state";
                }
               description "A Power State is a condition or mode of a device (or component)
                              that broadly characterizes its capabilities, power, and
                              responsiveness to input";
            }
        }
        leaf operState   {
            type uint32;
            config false;
            description "The current operational Power State";
        }
        leaf adminState   {
            type uint32;
            description "The desired Power State";
        }
        leaf reason  {
            type string;
            config false;
            description "Describes the reason for the adminState";
        }
        leaf configuredTime  {
            type yang:timestamp;
            config false;
            description "Indicates the time of the desired Power State.";
        }
        description "A Power State Set is a collection of Power States that comprises a
                           named or logical control grouping";
    }
   	   
    grouping energyGroup {
        container energyObject {
            leaf index {
                type uint32;
                description "An [RFC6933] entPhysicalIndex";
            }
            leaf name {
                if-feature eoObject-name;
                type string;
                description "An [RFC6933] entPhysicalName";
            }
            leaf identifier {
                type int64;
                description "An [RFC6933] entPhysicalUUID. NOTE: RFC 7326 indicates this is of type uuid";
            }
            leaf alternateKey {
                if-feature eoObject-alternateKey;
                type string;
                description "A manufacturer-defined string that can be used to identify the Energy Object";
            }
            leaf domainName {
                type string;
                description "The name of an Energy Management Domain for the Energy Object";
            }
            leaf role {
                type string;
                description "An administratively assigned name to indicate the purpose an
                     Energy Object serves in the network";
            }
            leaf keywords {
                type string;
                description "A list of keywords or [0..n] tags  that can be used to group Energy
                     Objects for reporting or searching";
            }
            leaf importance {
                type uint32;
                description "Specifies a ranking of howimportant the Energy Object is
                    (on a scale of 1 to 100) compared with other Energy Objects";
            }
            container relationships {
                list relationship {
                    config false;
                    leaf id {type int32;}
                    leaf relationshipType {
                        type enumeration {
                            enum METERS;
                            enum METEREDBY;
                            enum POWERS;
                            enum POWEREDBY;
                            enum AGGREGATES;
                            enum AGGREGATEDBY;
                        }
                        description "A description of the relationship";
                    }
                    leaf relationshipObject {
                        type int64;
                        description "unique name  for this instance";
                    }
                    description "collection of Relationship";
                }
            }
           container nameplate {
                container nominalPower {
                    uses powerMeasurement;
                    description "The nominal power of the Energy as specified by the device manufacturer";
                }
                leaf details {
                    type string;
                    description "An [RFC3986] URI that links to manufacturer information about the nominal power of a device";
                }
                description "The nominal PowerMeasurement of the Energy Object as specified by the device manufacturer";
            }
            container power {
                uses powerMeasurement;
                description "The present power measurement of the Energy Object";
            }
            container energy {
                if-feature eoObject-energy;
                uses energyMeasurement;
                description "The present energy measurement for the Energy Object";
            }
            container demand {
                if-feature eoObject-demand;
                uses demandMeasurement;
                description "power demand information over time.";
            }   
            container powerControls {     
                list powerControl {
                    leaf id {type int32;}
                    uses powerStateSet;
                    description "collection of PowerStateSet";
                }
                description "base class for device, powerInterface, and component";
            }
        }
    }
    	   
    container eoDevices {
        config false;
        list eoDevice {
            config false;
            leaf id {type int32;}
            leaf eocategory {
                config false;
                type enumeration {
                    enum PRODUCER {description "energy object category";}
                    enum CONSUMER {description "energy object category";}
                    enum METER {description "energy object category";}
                    enum DISTRIBUTOR {description "energy object category";}
                    enum STORE {description "energy object category";}
                }
                description "energy object category";
            }
            uses energyGroup;
            container powerInterfaces {
                list powerInterface {
                    leaf id {type int32;}
                    uses energyGroup;
                    description "collection of power interfaces";
                }
            }
            container components {
                list component {
                    leaf id {type int32;}
                    uses energyGroup;
                    description "collection of components";
                }
            }
        }
        description "root of enam api";
    }


    rpc poll-eoDevice {
        input {
            leaf deviceIP {type string;}
            leaf protocol {type string;}
            leaf numSamples {type int32;}
            leaf period {type int32;}
        }
        output {
            leaf response {type string;}
        }
        description "read an eoDevice and collect TimedMeasurements, and write into MD-SAL";
    }


}
