module odl-eman-energyobject {

  /*** NAMESPACE / PREFIX DEFINITION ***/
  namespace "urn:ietf:params:xml:ns:yang:opendaylight:eman:energyobject";
  prefix "energy-object";

  /*** LINKAGE (IMPORTS / INCLUDES) ***/
  import odl-eman-entity              { prefix "entity"; }
  import odl-eman-iana-energytypes    { prefix "iana-energytypes"; }
  import odl-eman-util                { prefix "eman-util"; }
  import ietf-yang-types              { prefix "yang"; revision-date "2013-07-15"; }
  import SNMPv2-TC                    { prefix "smiv2"; }

  /*** META INFORMATION ***/
  organization
   "IETF EMAN Working Group";

  contact
   "WG charter:
    http://datatracker.ietf.org/wg/eman/charter/

    Mailing Lists:
    General Discussion: eman@ietf.org

    To Subscribe:
    https://www.ietf.org/mailman/listinfo/eman

    Archive:
    http://www.ietf.org/mail-archive/web/eman

    Editors:
    Mouli Chandramouli
    Cisco Systems, Inc.
    Sarjapur Outer Ring Road
    Bangalore 560103
    India
    Phone: +91 80 4429 2409
    Email: moulchan@cisco.com

    Brad Schoening
    44 Rivers Edge Drive
    Little Silver, NJ 07739
    United States
    Email: brad.schoening@verizon.net

    Juergen Quittek
    NEC Europe, Ltd.
    NEC Laboratories Europe
    Network Research Division
    Kurfuersten-Anlage 36
    Heidelberg  69115
    Germany
    Phone: +49 6221 4342-115
    Email: quittek@neclab.eu

    Thomas Dietz
    NEC Europe, Ltd.
    NEC Laboratories Europe
    Network Research Division
    Kurfuersten-Anlage 36
    69115 Heidelberg
    Germany
    Phone: +49 6221 4342-128
    Email: Thomas.Dietz@nw.neclab.eu

    Benoit Claise
    Cisco Systems, Inc.
    De Kleetlaan 6a b1
    Degem 1831
    Belgium
    Phone:  +32 2 704 5622
    Email: bclaise@cisco.com";

  description
   "Copyright (c) 2015 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This MIB is used to monitor power and energy in
    devices.

    The tables eoMeterCapabilitiesTable and eoPowerTable
    are a sparse extension of the eoTable from the
    ENERGY-OBJECT-CONTEXT-MIB.  As a requirement,
    [RFC7461] SHOULD be implemented.

    Module Compliance of ENTITY-MIB v4 with respect to
    entity4CRCompliance MUST be supported which requires
    implementation of 4 MIB objects: entPhysicalIndex,
    entPhysicalClass, entPhysicalName and entPhysicalUUID.";

  revision "2015-02-09" {
    description
     "Initial version, published as RFC 7460.";
  }

  /*** TYPE DEFINITIONS ***/

  typedef UnitMultiplier {
    type enumeration {
      enum yocto { value -24; }
      enum zepto { value -21; }
      enum atto  { value -18; }
      enum femto { value -15; }
      enum pico  { value -12; }
      enum nano  { value -9; }
      enum micro { value -6; }
      enum milli { value -3; }
      enum units { value 0; }
      enum kilo  { value 3; }
      enum mega  { value 6; }
      enum giga  { value 9; }
      enum tera  { value 12; }
      enum peta  { value 15; }
      enum exa   { value 18; }
      enum zetta { value 21; }
      enum yotta { value 24; }
    }
    description
     "The Unit Multiplier is an integer value that represents
      the IEEE 61850 Annex A units multiplier associated with
      the integer units used to measure the power or energy.

      For example, when used with eoPowerUnitMultiplier, -3
      represents 10^-3 or milliwatts.";
    reference
     "The International System of Units (SI), National
      Institute of Standards and Technology, Spec. Publ. 330,
      August 1991.";
  }

  container energyObjectMibNotifs {

    leaf eoPowerEnableStatusNotification {
      type smiv2:TruthValue;
      config true;
      description
       "This object controls whether the system produces
        notifications for eoPowerStateChange.  A false value will
        prevent these notifications from being generated.";
    }

  }

  container energyObjectMibObjects {

    /* XXX table comments here XXX */
    list eoMeterCapabilitiesEntry {

      key "entPhysicalIndex";
      description
       "An entry describes the metering capability of an Energy
        Object.";

      /*** Was originally a keyref. ODL yangtools parser does not support keyref ***/
      leaf entPhysicalIndex {
        type leafref {
          path "/entity:entityPhysical/entity:entPhysicalEntry/entity:entPhysicalIndex";
        }
        config false;
        description
         "Automagically generated keyref leaf.";
      }

      leaf eoMeterCapability {
        type bits {
          bit none            { position 0; }
          bit powermetering   { position 1; }
          bit energymetering  { position 2; }
          bit powerattributes { position 3; }
        }
        config false;
        description
         "An indication of the energy-monitoring capabilities
          supported by this agent.  This object use a BITS syntax
          and indicates the MIB groups supported by the probe.  By
          reading the value of this object, it is possible to
          determine the MIB tables supported.";
      }
    }


    /* XXX table comments here XXX */

    list eoPowerEntry {

      key "entPhysicalIndex";
      description
       "An entry describes the power usage of an Energy Object.";

      /*** Was originally a keyref. ODL yangtools parser does not support keyref ***/
      leaf entPhysicalIndex {
        type leafref {
          path "/entity:entityPhysical/entity:entPhysicalEntry/entity:entPhysicalIndex";
        }
        config false;
        description
         "Automagically generated keyref leaf.";
      }

      leaf eoPower {
        type int32;
        units "watts";
        config false;
        description
         "This object indicates the power measured for the Energy
          Object.  For alternating current, this value is obtained
          as an average over fixed number of AC cycles.  This value
          is specified in SI units of watts with the magnitude of
          watts (milliwatts, kilowatts, etc.) indicated separately
          in eoPowerUnitMultiplier.  The accuracy of the measurement
          is specified in eoPowerAccuracy.  The direction of power
          flow is indicated by the sign on eoPower.  If the Energy
          Object is consuming power, the eoPower value will be
          positive.  If the Energy Object is producing power, the
          eoPower value will be negative.

          The eoPower MUST be less than or equal to the maximum
          power that can be consumed at the Power State specified
          by eoPowerState.

          The eoPowerMeasurementCaliber object specifies how the
          usage value reported by eoPower was obtained.  The eoPower
          value must report 0 if the eoPowerMeasurementCaliber is
          'unavailable'.  For devices that cannot measure or
          report power, this option can be used.";
      }

      leaf eoPowerNameplate {
        type uint32;
        units "watts";
        config false;
        description
         "This object indicates the rated maximum consumption for
          the fully populated Energy Object.  The nameplate power
          requirements are the maximum power numbers given in SI
          watts and, in almost all cases, are well above the
          expected operational consumption.  Nameplate power is
          widely used for power provisioning.  This value is
          specified in either units of watts or voltage and
          current.  The units are therefore SI watts or equivalent
          Volt-Amperes with the magnitude (milliwatts, kilowatts,
          etc.) indicated separately in eoPowerUnitMultiplier.";
      }

      leaf eoPowerUnitMultiplier {
        type energy-object:UnitMultiplier;
        config false;
        description
         "The magnitude of watts for the usage value in eoPower
          and eoPowerNameplate.";
      }

      leaf eoPowerAccuracy {
        type int32 {
          range "0..10000";
        }
        units "hundredths of percent";
        config false;
        description
         "This object indicates a percentage value, in hundredths of a
          percent, representing the assumed accuracy of the usage
          reported by eoPower.  For example, the value 1010 means
          the reported usage is accurate to +/- 10.1 percent.  This
          value is zero if the accuracy is unknown or not
          applicable based upon the measurement method.

          ANSI and IEC define the following accuracy classes for
          power measurement:
               IEC 62053-22 60044-1 class 0.1, 0.2, 0.5, 1  3.
               ANSI C12.20 class 0.2, 0.5";
      }

      leaf eoPowerMeasurementCaliber {
        type enumeration {
          enum unavailable { value 1; }
          enum unknown     { value 2; }
          enum actual      { value 3; }
          enum estimated   { value 4; }
          enum static      { value 5; }
        }
        config false;
        description
         "This object specifies how the usage value reported by
          eoPower was obtained:

          - unavailable(1): Indicates that the usage is not
          available.  In such a case, the eoPower value must be 0
          for devices that cannot measure or report power this
          option can be used.

          - unknown(2): Indicates that the way the usage was
          determined is unknown.  In some cases, entities report
          aggregate power on behalf of another device.  In such
          cases it is not known whether the usage reported is
          actual, estimated, or static.

          - actual(3):  Indicates that the reported usage was
          measured by the entity through some hardware or direct
          physical means.  The usage data reported is not estimated
          or static but is the measured consumption rate.

          - estimated(4): Indicates that the usage was not
          determined by physical measurement.  The value is a
          derivation based upon the device type, state, and/or
          current utilization using some algorithm or heuristic.  It
          is presumed that the entity's state and current
          configuration were used to compute the value.

          - static(5): Indicates that the usage was not determined
          by physical measurement, algorithm, or derivation.  The
          usage was reported based upon external tables,
          specifications, and/or model information.  For example, a
          PC Model X draws 200W, while a PC Model Y draws 210W.";
      }

      leaf eoPowerCurrentType {
        type enumeration {
          enum ac      { value 1; }
          enum dc      { value 2; }
          enum unknown { value 3; }
        }
        config false;
        description
         "This object indicates whether the eoPower for the
          Energy Object reports alternating current 'ac', direct
          current 'dc', or that the current type is unknown.";
      }

      leaf eoPowerMeasurementLocal {
        type smiv2:TruthValue;
        config false;
        description
         "This object indicates the source of power measurement
          and can be useful when modeling the power usage of
          attached devices.  The power measurement can be performed
          by the entity itself or the power measurement of the
          entity can be reported by another trusted entity using a
          protocol extension.  A value of true indicates the
          measurement is performed by the entity, whereas false
          indicates that the measurement was performed by another
          entity.";
      }

      leaf eoPowerAdminState {
        type iana-energytypes:PowerStateSet;
        config true;
        description
         "This object specifies the desired Power State and the
          Power State Set for the Energy Object.  Note that other(0)
          is not a Power State Set and unknown(255) is not a Power
          State as such, but simply an indication that the Power
          State of the Energy Object is unknown.
          Possible values of eoPowerAdminState within the Power
          State Set are registered at IANA.
          A current list of assignments can be found at
          ";
      }

      leaf eoPowerOperState {
        type iana-energytypes:PowerStateSet;
        config false;
        description
         "This object specifies the current operational Power
          State and the Power State Set for the Energy Object.
          other(0) is not a Power State Set and unknown(255) is not
          a Power State as such, but simply an indication that the
          Power State of the Energy Object is unknown.

          Possible values of eoPowerOperState within the Power
          State Set are registered at IANA.  A current list of
          assignments can be found at
          ";
      }

      leaf eoPowerStateEnterReason {
        type eman-util:OwnerString;
        config true;
        description
         "This string object describes the reason for the
          eoPowerAdminState transition.  Alternatively, this string
          may contain with the entity that configured this Energy
          Object to this Power State.";
      }
    }


    /* XXX table comments here XXX */

    list eoPowerStateEntry {

      key "entPhysicalIndex eoPowerStateIndex";
      description
       "A eoPowerStateEntry extends a corresponding
        eoPowerEntry.  This entry displays max usage values at
        every single possible Power State supported by the Energy
        Object.
        For example, given the values of a Energy Object
        corresponding to a maximum usage of 0 W at the
        state emanmechoff, 8 W at state 6 (ready), 11 W at state
        emanmediumMinus, and 11 W at state emanhigh:

                State      MaxUsage Units
             emanmechoff       0       W
             emansoftoff       0       W
             emanhibernate     0       W
             emansleep         0       W
             emanstandby       0       W
             emanready         8       W
             emanlowMinus      8       W
             emanlow          11       W
             emanmediumMinus  11       W
             emanmedium       11       W
             emanhighMinus    11       W
             emnanhigh        11       W

        Furthermore, this table also includes the total time in
        each Power State, along with the number of times a
        particular Power State was entered.";

      /*** Was originally a keyref. ODL yangtools parser does not support keyref ***/
      leaf entPhysicalIndex {
        type leafref {
          path "/entity:entityPhysical/entity:entPhysicalEntry/entity:entPhysicalIndex";
        }
        config false;
        description
         "Automagically generated keyref leaf.";
      }

      leaf eoPowerStateIndex {
        type iana-energytypes:PowerStateSet;
        config false;
        description
         "This object specifies the index of the Power State of
          the Energy Object within a Power State Set.  The semantics
          of the specific Power State can be obtained from the
          Power State Set definition.";
      }

      leaf eoPowerStateMaxPower {
        type int32;
        units "watts";
        config false;
        description
         "This object indicates the maximum power for the Energy
          Object at the particular Power State.  This value is
          specified in SI units of watts with the magnitude of the
          units (milliwatts, kilowatts, etc.) indicated separately
          in eoPowerStatePowerUnitMultiplier.  If the maximum power
          is not known for a certain Power State, then the value is
          encoded as 0xFFFFFFFF.

          For Power States not enumerated, the value of
          eoPowerStateMaxPower might be interpolated by using the
          next highest supported Power State.";
      }

      leaf eoPowerStatePowerUnitMultiplier {
        type energy-object:UnitMultiplier;
        config false;
        description
         "The magnitude of watts for the usage value in
          eoPowerStateMaxPower.";
      }

      leaf eoPowerStateTotalTime {
        type yang:timeticks;
        config false;
        description
         "This object indicates the total time in hundredths
          of a second that the Energy Object has been in this power
          state since the last reset, as specified in the
          sysUpTime.";
      }

      leaf eoPowerStateEnterCount {
        type yang:counter32;
        config false;
        description
         "This object indicates how often the Energy Object has
          entered this power state, since the last reset of the
          device as specified in the sysUpTime.";
      }
    }


    /* XXX table comments here XXX */

    list eoEnergyParametersEntry {

      key "entPhysicalIndex eoEnergyParametersIndex";
      description
       "An entry controls an energy measurement in
        eoEnergyTable.";

      /*** Was originally a keyref. ODL yangtools parser does not support keyref ***/
      leaf entPhysicalIndex {
        type leafref {
          path "/entity:entityPhysical/entity:entPhysicalEntry/entity:entPhysicalIndex";
        }
        config false;
        description
         "Automagically generated keyref leaf.";
      }

      leaf eoEnergyParametersIndex {
        type int32 {
          range "1..2147483647";
        }
        config false;
        description
         "This object specifies the index of the Energy Parameters
          setting for collection of energy measurements for an
          Energy Object.  An Energy Object can have multiple
          eoEnergyParametersIndex, depending on the capabilities of
          the Energy Object";
      }

      leaf eoEnergyParametersIntervalLength {
        type smiv2:TimeInterval;
        config true;
        description
         "This object indicates the length of time in hundredths
          of a second over which to compute the average
          eoEnergyConsumed measurement in the eoEnergyTable table.
          The computation is based on the Energy Object's internal
          sampling rate of power consumed or produced by the Energy
          Object.  The sampling rate is the rate at which the Energy
          Object can read the power usage and may differ based on
          device capabilities.  The average energy consumption is
          then computed over the length of the interval.  The
          default value of 15 minutes is a common interval used in
          industry.";
      }

      leaf eoEnergyParametersIntervalNumber {
        type uint32;
        config true;
        description
         "The number of intervals maintained in the eoEnergyTable.
          Each interval is characterized by a specific
          eoEnergyCollectionStartTime, used as an index to the
          table eoEnergyTable.  Whenever the maximum number of
          entries is reached, the measurement over the new interval
          replaces the oldest measurement.  There is one exception
          to this rule: when the eoEnergyMaxConsumed and/or
          eoEnergyMaxProduced are in (one of) the two oldest
          measurement(s), they are left untouched and the next
          oldest measurement is replaced.";
      }

      leaf eoEnergyParametersIntervalMode {
        type enumeration {
          enum period  { value 1; }
          enum sliding { value 2; }
          enum total   { value 3; }
        }
        config true;
        description
         "A control object to define the mode of interval
          calculation for the computation of the average
          eoEnergyConsumed or eoEnergyProvided measurement in the
          eoEnergyTable table.

          A mode of period(1) specifies non-overlapping periodic
          measurements.

          A mode of sliding(2) specifies overlapping sliding
          windows where the interval between the start of one
          interval and the next is defined in
          eoEnergyParametersIntervalWindow.

          A mode of total(3) specifies non-periodic measurement.
          In this mode only one interval is used as this is a
          continuous measurement since the last reset.  The value of
          eoEnergyParametersIntervalNumber should be (1) one and
          eoEnergyParametersIntervalLength is ignored.";
      }

      leaf eoEnergyParametersIntervalWindow {
        type smiv2:TimeInterval;
        config true;
        description
         "The length of the duration window between the starting
          time of one sliding window and the next starting time in
          hundredths of seconds, used to compute the average of
          eoEnergyConsumed, eoEnergyProvided measurements in the
          eoEnergyTable table.  This is valid only when the
          eoEnergyParametersIntervalMode is sliding(2).  The
          eoEnergyParametersIntervalWindow value should be a
          multiple of eoEnergyParametersSampleRate.";
      }

      leaf eoEnergyParametersSampleRate {
        type uint32;
        units "Milliseconds";
        config true;
        description
         "The sampling rate, in milliseconds, at which the Energy
          Object should poll power usage in order to compute the
          average eoEnergyConsumed, eoEnergyProvided measurements
          in the table eoEnergyTable.  The Energy Object should
          initially set this sampling rate to a reasonable value,
          i.e., a compromise between intervals that will provide
          good accuracy by not being too long, but not so short
          that they affect the Energy Object performance by
          requesting continuous polling.  If the sampling rate is
          unknown, the value 0 is reported.  The sampling rate
          should be selected so that
          eoEnergyParametersIntervalWindow is a multiple of
          eoEnergyParametersSampleRate.  The default value is one
          second.";
      }

      leaf eoEnergyParametersStorageType {
        type smiv2:StorageType;
        config true;
        description
         "This variable indicates the storage type for this row.";
      }

      leaf eoEnergyParametersStatus {
        type smiv2:RowStatus;
        config true;
        description
         "The status of this row.  The eoEnergyParametersStatus is
          used to start or stop energy usage logging.  An entry
          status may not be active(1) unless all objects in the
          entry have an appropriate value.  If this object is not
          equal to active, all associated usage-data logged into
          the eoEnergyTable will be deleted.  The data can be
          destroyed by setting up the eoEnergyParametersStatus to
          destroy.";
      }
    }


    /* XXX table comments here XXX */

    list eoEnergyEntry {

      key "eoEnergyParametersIndex eoEnergyCollectionStartTime";
      description
       "An entry describing energy measurements.";

      /*** Was originally a keyref. ODL yangtools parser does not support keyref ***/
      leaf eoEnergyParametersIndex {
        type leafref {
          path "/energy-object:energyObjectMibObjects/energy-object:eoEnergyParametersEntry/energy-object:eoEnergyParametersIndex";
        }
        config true;
        description
         "Automagically generated keyref leaf.";
      }

      leaf eoEnergyCollectionStartTime {
        type yang:timeticks;
        units "hundredths of a second";
        config false;
        description
         "The time (in hundredths of a second) since the
          network management portion of the system was last
          re-initialized, as specified in the sysUpTime RFC 3418.
          This object specifies the start time of the energy
          measurement sample.";
        reference
         "RFC 3418: Management Information Base (MIB) for the
          Simple Network Management Protocol (SNMP)";
      }

      leaf eoEnergyConsumed {
        type uint32;
        units "Watt-hours";
        config false;
        description
         "This object indicates the energy consumed in units of
          watt-hours for the Energy Object over the defined
          interval.  This value is specified in the common billing
          units of watt-hours with the magnitude of watt-hours
          kWh, MWh, etc.) indicated separately in
          eoEnergyUnitMultiplier.";
      }

      leaf eoEnergyProvided {
        type uint32;
        units "Watt-hours";
        config false;
        description
         "This object indicates the energy produced in units of
          watt-hours for the Energy Object over the defined
          interval.

          This value is specified in the common billing units of
          watt-hours with the magnitude of watt-hours (kWh, MWh,
          etc.) indicated separately in
          eoEnergyUnitMultiplier.";
      }

      leaf eoEnergyStored {
        type uint32;
        units "Watt-hours";
        config false;
        description
         "This object indicates the difference of the energy
          consumed and energy produced for an Energy Object in
          units of watt-hours for the Energy Object over the
          defined interval.  This value is specified in the common
          billing units of watt-hours with the magnitude of
          watt-hours (kWh, MWh, etc.) indicated separately in
          eoEnergyUnitMultiplier.";
      }

      leaf eoEnergyUnitMultiplier {
        type energy-object:UnitMultiplier;
        config false;
        description
         "This object is the magnitude of watt-hours for the
          energy field in eoEnergyConsumed, eoEnergyProvided,
          eoEnergyStored, eoEnergyMaxConsumed, and
          eoEnergyMaxProduced.";
      }

      leaf eoEnergyAccuracy {
        type int32 {
          range "0..10000";
        }
        units "hundredths of percent";
        config false;
        description
         "This object indicates a percentage accuracy, in hundredths
          of a percent, of Energy usage reporting.  eoEnergyAccuracy
          is applicable to all Energy measurements in the
          eoEnergyTable.

          For example, 1010 means the reported usage is accurate to
          +/- 10.1 percent.

          This value is zero if the accuracy is unknown.";
      }

      leaf eoEnergyMaxConsumed {
        type uint32;
        units "Watt-hours";
        config false;
        description
         "This object is the maximum energy observed in
          eoEnergyConsumed since the monitoring started or was
          reinitialized.  This value is specified in the common
          billing units of watt-hours with the magnitude of
          watt-hours (kWh, MWh, etc.) indicated separately in
          eoEnergyUnitMultiplier.";
      }

      leaf eoEnergyMaxProduced {
        type uint32;
        units "Watt-hours";
        config false;
        description
         "This object is the maximum energy ever observed in
          eoEnergyEnergyProduced since the monitoring started.  This
          value is specified in the units of watt-hours with the
          magnitude of watt-hours (kWh, MWh, etc.) indicated
          separately in eoEnergyEnergyUnitMultiplier.";
      }

      leaf eoEnergyDiscontinuityTime {
        type yang:timestamp;
        config false;
        description
         "The value of sysUpTime RFC 3418 on the most recent
          occasion at which any one or more of this entity's energy
          counters in this table suffered a discontinuity:
          eoEnergyConsumed, eoEnergyProvided or eoEnergyStored.  If
          no such discontinuities have occurred since the last
          re-initialization of the local management subsystem, then
          this object contains a zero value.";
        reference
         "RFC 3418: Management Information Base (MIB) for the
          Simple Network Management Protocol (SNMP)";
      }
    }
  }

  notification eoPowerStateChange {
    description
     "The SNMP entity generates the eoPowerStateChange when
      the values of eoPowerAdminState or eoPowerOperState,
      in the context of the Power State Set, have changed for
      the Energy Object represented by the entPhysicalIndex.";

    container eoPowerStateChange-eoPowerAdminState {
        /*** Was originally a keyref. ODL yangtools parser does not support keyref ***/
     leaf entPhysicalIndex {
        type leafref {
          path "/entity:entityPhysical/entity:entPhysicalEntry/entity:entPhysicalIndex";
        }
        config false;
        description
         "Automagically generated keyref leaf.";
      }
      leaf eoPowerAdminState {
        type iana-energytypes:PowerStateSet;
        config false;
        description
         "This object specifies the desired Power State and the
          Power State Set for the Energy Object.  Note that other(0)
          is not a Power State Set and unknown(255) is not a Power
          State as such, but simply an indication that the Power
          State of the Energy Object is unknown.
          Possible values of eoPowerAdminState within the Power
          State Set are registered at IANA.
          A current list of assignments can be found at
          ";
      }
    }

    container eoPowerStateChange-eoPowerOperState {
        /*** Was originally a keyref. ODL yangtools parser does not support keyref ***/
     leaf entPhysicalIndex {
        type leafref {
          path "/entity:entityPhysical/entity:entPhysicalEntry/entity:entPhysicalIndex";
        }
        config false;
        description
         "Automagically generated keyref leaf.";
      }
      leaf eoPowerOperState {
        type iana-energytypes:PowerStateSet;
        config false;
        description
         "This object specifies the current operational Power
          State and the Power State Set for the Energy Object.
          other(0) is not a Power State Set and unknown(255) is not
          a Power State as such, but simply an indication that the
          Power State of the Energy Object is unknown.

          Possible values of eoPowerOperState within the Power
          State Set are registered at IANA.  A current list of
          assignments can be found at
          ";
      }
    }

    container eoPowerStateChange-eoPowerStateEnterReason {
        /*** Was originally a keyref. ODL yangtools parser does not support keyref ***/
      leaf entPhysicalIndex {
        type leafref {
          path "/entity:entityPhysical/entity:entPhysicalEntry/entity:entPhysicalIndex";
        }
        config false;
        description
         "Automagically generated keyref leaf.";
      }

      leaf eoPowerStateEnterReason {
        type eman-util:OwnerString;
        config false;
        description
         "This string object describes the reason for the


          eoPowerAdminState transition.  Alternatively, this string
          may contain with the entity that configured this Energy
          Object to this Power State.";
      }
    }
  }
} /* end of module odl-eman-energyobject */
