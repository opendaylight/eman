module odl-eman-iana-energytypes {

  /*** NAMESPACE / PREFIX DEFINITION ***/
  namespace "urn:opendaylight:params:xml:ns:yang:eman:iana:energytypes";
  prefix "iana-energytypes";

  /*** LINKAGE (IMPORTS / INCLUDES) ***/

  /*** META INFORMATION ***/
  organization
   "IANA";

  contact
   "Internet Assigned Numbers Authority
    Postal: ICANN
            12025 Waterfront Drive, Suite 300
            Los Angeles, CA 90094-2536
            United States
    Phone: +1-310-301-5800
    EMail: iana@iana.org";

  description
   "This MIB module defines TEXTUAL-CONVENTIONs that specify:

    IANAPhysicalClass - an indication of the general hardware
    type of a particular physical entity;

    PowerStateSet - which specifies the Power State Sets and
    Power State Set Values an Energy Object supports.

    IANAEnergyRelationship - that describes the relationships
    between Energy Objects.

    Copyright (c) 2015 IETF Trust and the persons identified as
    authors of the code.  All rights reserved.

    Redistribution and use in source and binary forms, with or
    without modification, is permitted pursuant to, and subject
    to the license terms contained in, the Simplified BSD
    License set forth in Section 4.c of the IETF Trust's Legal
    Provisions Relating to IETF Documents
    (http://trustee.ietf.org/license-info).

    The initial version of the IANAPhysicalClass MIB module was
	published in RFC 6933; for full legal notices see the RFC
	itself.

	The initial version of the PowerStateSet MIB module was
	published in RFC 7460; for full legal notices see the RFC
	itself.

	The initial version of the IANAEnergyRelationship MIB module
	was published in RFC 7461; for full legal notices see the
	RFC itself.";


  revision "2013-04-05" {
    description
     "Initial version of this MIB as published in
      RFC 6933.";
  }

  /*** TYPE DEFINITIONS ***/
  typedef IANAPhysicalClass {
    type enumeration {
      enum other        { value 1; }
      enum unknown      { value 2; }
      enum chassis      { value 3; }
      enum backplane    { value 4; }
      enum container    { value 5; }
      enum powerSupply  { value 6; }
      enum fan          { value 7; }
      enum sensor       { value 8; }
      enum module       { value 9; }
      enum port         { value 10; }
      enum stack        { value 11; }
      enum cpu          { value 12; }
      enum energyObject { value 13; }
      enum battery      { value 14; }
    }
    description
     "An enumerated value that provides an indication of the
      general hardware type of a particular physical entity.
      There are no restrictions as to the number of
      entPhysicalEntries of each entPhysicalClass, which must
      be instantiated by an agent.

      The enumeration 'other' is applicable if the physical
      entity class is known but does not match any of the
      supported values.

      The enumeration 'unknown' is applicable if the physical
      entity class is unknown to the agent.

      The enumeration 'chassis' is applicable if the physical
      entity class is an overall container for networking
      equipment.  Any class of physical entity, except a stack,
      may be contained within a chassis; a chassis may only
      be contained within a stack.

      The enumeration 'backplane' is applicable if the physical
      entity class is some sort of device for aggregating and
      forwarding networking traffic, such as a shared
      backplane in a modular ethernet switch.  Note that an
      agent may model a backplane as a single physical entity,
      which is actually implemented as multiple discrete
      physical components (within a chassis or stack).

      The enumeration 'container' is applicable if the
      physical entity class is capable of containing one or
      more removable physical entities, possibly of different
      types.  For example, each (empty or full) slot in a
      chassis will be modeled as a container.  Note that all
      removable physical entities should be modeled within
      a container entity, such as field-replaceable modules,
      fans, or power supplies.  Note that all known containers
      should be modeled by the agent, including empty
      containers.

      The enumeration 'powerSupply' is applicable if the
      physical entity class is a power-supplying component.

      The enumeration 'fan' is applicable if the physical
      entity class is a fan or other heat-reduction component.

      The enumeration 'sensor' is applicable if the physical
      entity class is some sort of sensor, such as a
      temperature sensor within a router chassis.

      The enumeration 'module' is applicable if the physical
      entity class is some sort of self-contained sub-system.
      If the enumeration 'module' is removable, then it should
      be modeled within a container entity; otherwise, it
      should be modeled directly within another physical
      entity (e.g., a chassis or another module).

      The enumeration 'port' is applicable if the physical
      entity class is some sort of networking port, capable
      of receiving and/or transmitting networking traffic.

      The enumeration 'stack' is applicable if the physical
      entity class is some sort of super-container (possibly
      virtual) intended to group together multiple chassis
      entities.  A stack may be realized by a 'virtual' cable,
      a real interconnect cable attached to multiple chassis,
      or multiple interconnect cables.  A stack should not be
      modeled within any other physical entities, but a stack
      may be contained within another stack.  Only chassis
      entities should be contained within a stack.

      The enumeration 'cpu' is applicable if the physical
      entity class is some sort of central processing unit.

      The enumeration 'energyObject' is applicable if the
      physical entity is some sort of energy object, i.e.,
      a piece of equipment that is part of or attached to
      a communications network that is monitored, controlled,
      or aids in the management of another device for Energy
      Management.

      The enumeration 'battery' is applicable if the physical
      entity class is some sort of battery.";
  }


  typedef PowerStateSet {
    type enumeration {
      enum other                         { value 0; }
      enum unknown                       { value 255; }
      enum ieee1621                      { value 256; }
      enum ieee1621Off                   { value 257; }
      enum ieee1621Sleep                 { value 258; }
      enum ieee1621On                    { value 259; }
      enum dmtf                          { value 512; }
      enum dmtfOn                        { value 513; }
      enum dmtfSleepLight                { value 514; }
      enum dmtfSleepDeep                 { value 515; }
      enum dmtfOffHard                   { value 516; }
      enum dmtfOffSoft                   { value 517; }
      enum dmtfHibernate                 { value 518; }
      enum dmtfPowerOffSoft              { value 519; }
      enum dmtfPowerOffHard              { value 520; }
      enum dmtfMasterBusReset            { value 521; }
      enum dmtfDiagnosticInterrapt       { value 522; }
      enum dmtfOffSoftGraceful           { value 523; }
      enum dmtfOffHardGraceful           { value 524; }
      enum dmtfMasterBusResetGraceful    { value 525; }
      enum dmtfPowerCycleOffSoftGraceful { value 526; }
      enum dmtfPowerCycleHardGraceful    { value 527; }
      enum eman                          { value 1024; }
      enum emanMechOff                   { value 1025; }
      enum emanSoftOff                   { value 1026; }
      enum emanHibernate                 { value 1027; }
      enum emanSleep                     { value 1028; }
      enum emanStandby                   { value 1029; }
      enum emanReady                     { value 1030; }
      enum emanLowMinus                  { value 1031; }
      enum emanLow                       { value 1032; }
      enum emanMediumMinus               { value 1033; }
      enum emanMedium                    { value 1034; }
      enum emanHighMinus                 { value 1035; }
      enum emanHigh                      { value 1036; }
    }
    description
     "IANAPowerState is a textual convention that describes
      Power State Sets and Power State Set Values an Energy
      Object supports.  IANA has created a registry of Power
      State supported by an Energy Object and IANA shall
      administer the list of Power State Sets and Power
      States.

      The Textual Convention assumes that Power States in a
      Power State Set are limited to 255 distinct values.  For
      a Power State Set S, the named number with the value S *
      256 is allocated to indicate the Power State Set.  For a
      Power State X in the Power State Set S, the named number
      with the value S * 256 + X + 1 is allocated to represent
      the Power State.

      Requests for new values should be made to IANA via email
      (iana@iana.org).";
    reference
     "http://www.iana.org/assignments/power-state-sets";
  }

  typedef IANAEnergyRelationship {
    type enumeration {
	  enum poweredBy    { value 1; }
	  enum powering     { value 2; }
	  enum meteredBy    { value 3; }
	  enum metering     { value 4; }
	  enum aggregatedBy { value 5; }
	  enum aggregating  { value 6; }
	}
    description
	 "An enumerated value specifying the type of
	  relationship between an Energy Object A, on
	  which the relationship is specified, with the
	  Energy Object B, identified by the UUID.

	  The enumeration 'poweredBy' is applicable if
	  Energy Object A is poweredBy Energy Object B.

	  The enumeration 'powering' is applicable if
	  Energy Object A is powering Energy Object B.

	  The enumeration 'meteredBy' is applicable if
	  Energy Object A is meteredBy Energy Object B.

	  The enumeration 'metering' is applicable if
	  Energy Object A is metering Energy Object B.

	  The enumeration 'aggregatedBy' is applicable if
	  Energy Object A is aggregatedBy Energy Object B.

	  The enumeration 'aggregating' is applicable if
	  Energy Object A is aggregating Energy Object B.";
  }
} /* end of module odl-eman-iana-energytypes */
