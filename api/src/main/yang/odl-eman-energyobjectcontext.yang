module odl-eman-energyobjectcontext {

  /*** NAMESPACE / PREFIX DEFINITION ***/
  namespace "urn:ietf:params:xml:ns:yang:opendaylight:eman:energyobjectcontext";
  prefix "energy-object";

  /*** LINKAGE (IMPORTS / INCLUDES) ***/
  import odl-eman-entity               { prefix "entity"; }
  import odl-eman-iana-energytypes     { prefix "iana-energytypes"; }
  import odl-eman-util                 { prefix "eman-util"; }
  import odl-eman-uuid-tc              { prefix "uuid-tc"; }
  import ieee-types                    { prefix "ieee"; }
  import INET-ADDRESS-MIB              { prefix "inet-address"; }
  import SNMPv2-TC                     { prefix "smiv2"; }

  /*** META INFORMATION ***/
  organization
   "IETF EMAN Working Group";

  contact
   "WG Charter:
    http://datatracker.ietf.org/wg/eman/charter/

    Mailing Lists:
    General Discussion: eman@ietf.org
    To Subscribe: https://www.ietf.org/mailman/listinfo/eman
    Archive: http://www.ietf.org/mail-archive/web/eman

    Editors:
      John Parello
      Cisco Systems, Inc.
      3550 Cisco Way
      San Jose, California 95134
      United States
      Phone: +1 408 525 2339
      Email: jparello@cisco.com

      Benoit Claise
      Cisco Systems, Inc.
      De Kleetlaan 6a b1
      Degem 1831
      Belgium
      Phone:  +32 2 704 5622
      Email: bclaise@cisco.com

      Mouli Chandramouli
      Cisco Systems, Inc.
      Sarjapur Outer Ring Road
      Bangalore 560103
      India
      Phone: +91 80 4429 2409
      Email: moulchan@cisco.com";

  description
   "Copyright (c) 2015 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This MIB is used for describing the identity and the
    context information of Energy Objects.";

  revision "2015-02-09" {
    description
     "Initial version, published as RFC 7461.";
  }

  /*** TYPE DEFINITIONS ***/

  typedef PethPsePortIndexOrZero {
    type int32 {
      range "0..2147483647";
    }
    description
     "This textual convention is an extension of the
      pethPsePortIndex convention, which defines a greater-
      than-zero value used to identify a power Ethernet Power
      Sourcing Equipment (PSE) port.

      This extension permits the additional value of zero.  The
      semantics of the value zero are object-specific and must,
      therefore, be defined as part of the description of any
      object that uses this syntax.  Examples of the usage of
      this extension are situations where none or all physical
      entities need to be referenced.";
  }

  typedef PethPsePortGroupIndexOrZero {
    type int32 {
      range "0..2147483647";
    }
    description
     "This textual convention is an extension of the
      pethPsePortGroupIndex convention from the Power Over
      Ethernet MIB in RFC 3621, which defines a greater-than-zero
      value used to identify the group containing the port to which
      a power Ethernet PSE is connected.  This extension
      permits the additional value of zero.  The semantics of
      the value zero are object-specific and must, therefore,
      be defined as part of the description of any object that
      uses this syntax.  Examples of the usage of this
      extension are situations where none or all physical
      entities need to be referenced.";
  }

  typedef LldpPortNumberOrZero {
    type int32 {
      range "0..4096";
    }
    description
     "This textual convention is an extension of the
      LldpPortNumber convention specified in the LLDP MIB,
      which defines a greater than zero value used to uniquely
      identify each port contained in the chassis (that is
      known to the LLDP agent) by a port number.  This
      extension permits the additional value of zero.  The
      semantics of the value zero are object-specific and must,
      therefore, be defined as part of the description of any
      object that uses this syntax.  Examples of the usage of
      this extension are situations where none or all physical
      entities need to be referenced.";
  }

  typedef EnergyObjectKeywordList {
    type binary {
      length "0..2048";
    }
    description
     "A list of keywords that can be used to group Energy
      Objects for reporting or searching.  If multiple keywords
      are present, then this string will contain all the
      keywords separated by the ',' character.  All alphanumeric
      characters and symbols (other than a comma), such as #,
      (, $, !, and &, are allowed.  White spaces before and
      after the commas are ignored, as well as within a keyword
      itself.

      For example, if an Energy Object were to be tagged with
      the keyword values 'hospitality' and 'guest', then the
      keyword list will be 'hospitality,guest'.";
  }

  container energyObjectContextMIBObjects {

    /* XXX table comments here XXX */
    list eoEntry {
      key "entPhysicalIndex";
      description
       "An entry describes the attributes of an Energy Object.
        Whenever a new Energy Object is added or an existing
        Energy Object is deleted, a row in the eoTable is added
        or deleted.";

      /*** Was originally a keyref. ODL yangtools parser does not support keyref ***/
      leaf entPhysicalIndex {
        type leafref {
          path "/entity:entityPhysical/entity:entPhysicalEntry/entity:entPhysicalIndex";
        }
        config false;
        description
         "Automagically generated keyref leaf.";
      }

      leaf eoEthPortIndex {
        type energy-object:PethPsePortIndexOrZero;
        config false;
        description
         "This variable uniquely identifies the power Ethernet
          port to which a Power over Ethernet device is connected.
          If the Power over Ethernet MIB in RFC 3621 is supported by
          the SNMP agent managing the Energy Object, then the
          Energy Object eoethPortIndex MUST contain the
          corresponding value of pethPsePortIndex.  If such a power
          Ethernet port cannot be specified or is not known, then
          the object is zero.";
        reference
         "RFC 3621: Power Ethernet MIB";
      }

      leaf eoEthPortGrpIndex {
        type energy-object:PethPsePortGroupIndexOrZero;
        config false;
        description
         "This variable uniquely identifies the group containing
          the port to which a power over Ethernet device PSE is
          connected (RFC 3621).  If the Power over Ethernet MIB (RFC
          3621) is supported by the SNMP agent managing the Energy
          Object, then the Energy Object eoEthPortGrpIndex MUST
          contain the corresponding value of eoethPortGrpIndex.  If
          such a power Ethernet port cannot be specified or is not
          known, then the object is zero.";
        reference
         "RFC 3621: Power Ethernet MIB";
      }

      leaf eoLldpPortNumber {
        type energy-object:LldpPortNumberOrZero;
        config false;
        description
         "This variable uniquely identifies the port component
          (contained in the local chassis with the LLDP agent) as
          defined by the lldpLocPortNum in the LLDP-MIB and
          LLDP-MED-MIB.  If the LLDP-MIB is supported by the
          SNMP agent managing the Energy Object, then the Energy
          Object eoLldpPortNumber MUST contain the corresponding
          value of lldpLocPortNum from the LLDP-MIB.  If such a
          port number cannot be specified or is not known, then the
          object is zero.";
        reference
         "LLDP MIB, IEEE 802.1AB-2005; LLDP-MED-MIB, ANSI/TIA-1057";
      }


      leaf eoMgmtMacAddress {
        type ieee:mac-address;
        config false;
        description
         "This object specifies a Media Access Control (MAC) address
          of the Energy Object.";
      }

      leaf eoMgmtAddressType {
        type inet-address:InetAddressType;
        config false;
        description
         "This object specifies the eoMgmtAddress type, i.e., an
          IPv4 or IPv6 address.  This object MUST be
          populated when eoMgmtAddress is populated.";
      }

      leaf eoMgmtAddress {
        type inet-address:InetAddress;
        config false;
        description
         "This object specifies the management address as an IPv4
          address or IPv6 address of Energy Object.  The IP address
          type, i.e. IPv4 or IPv6, is determined by the
          eoMgmtAddressType value.  This object can be used as an
          alternate key to help link the Energy Object with other
          keyed information that may be stored within the EnMS(s).";
      }

      leaf eoMgmtDNSName {
        type binary;
        config false;
        description
         "This object specifies a DNS name of the eoMgmtAddress.
          This object can be used as an alternate key to help link
          the Energy Object with other keyed information that may
          be stored within the EnMS(s).  A DNS Name must always be a
          fully qualified name.  This MIB uses the same encoding as
          the DNS protocol.";
        reference
         "RFC 1034: Domain names - concepts and facilities,
          Section 3.1.";
      }

      leaf eoDomainName {
        type eman-util:SnmpAdminString;
        config true;
        description
         "This object specifies the name of an Energy Management
          Domain for the Energy Object.  By default, this object
          should be an empty string.  The value of eoDomainName must
          remain constant at least from one re-initialization of
          the entity local management system to the next re-
          initialization.";
      }

      leaf eoRoleDescription {
        type eman-util:SnmpAdminString;
        config true;
        description
         "This object specifies an administratively assigned name
          to indicate the purpose an Energy Object serves in the
          network.

          For example, we can have a phone deployed to a lobby with
          eoRoleDescription as 'Lobby phone'.

          This object specifies that the value is the zero-length
          string value if no role description is configured.
          The value of eoRoleDescription must remain constant at
          least from one re-initialization of the entity local
          management system to the next re-initialization.";
      }

      leaf eoKeywords {
        type energy-object:EnergyObjectKeywordList;
        config true;
        description
         "This object specifies a list of keywords that can be
          used to group Energy Objects for reporting or searching.
          The value is the zero-length string if no keywords have
          been configured.  If multiple keywords are present, then
          this string will contain all the keywords separated by
          the ',' character.  For example, if an Energy Object were
          to be tagged with the keyword values 'hospitality' and
          'guest', then the keyword list will be
          'hospitality,guest'.

          If write access is implemented and a value is written
          into the instance, the agent must retain the supplied
          value in the eoKeywords instance associated with
          the same physical entity for as long as that entity
          remains instantiated.  This includes instantiations
          across all re-initializations/reboots of the local
          management agent.";
      }

      leaf eoImportance {
        type int32 {
          range "1..100";
        }
        config true;
        description
         "This object specifies a ranking of how important the
          Energy Object is (on a scale of 1 to 100) compared with
          other Energy Objects in the same Energy Management
          Domain.  The ranking should provide a business or
          operational context for the Energy Object as compared to
          other similar Energy Objects.  This ranking could be used
          as input for policy-based network management.

          Although network managers must establish their own
          ranking, the following is a broad recommendation:

          90 to 100 Emergency response
          80 to 89  Executive or business critical
          70 to 79  General or average
          60 to 69  Staff or support
          40 to 59  Public or guest
           1 to 39  Decorative or hospitality

          The value of eoImportance must remain constant at least
          from one re-initialization of the Energy Object local
          management system to the next re-initialization.";
      }

      leaf eoPowerCategory {
        type enumeration {
          enum consumer    { value 0; }
          enum producer    { value 1; }
          enum meter       { value 2; }
          enum distributor { value 3; }
          enum store       { value 4; }
        }
        config false;
        description
         "This object describes the Energy Object category, which
          indicates the expected behavior or physical property of
          the Energy Object, based on its design.  An Energy Object
          can be a consumer(0), producer(1), meter(2),
          distributor(3), or store(4).

          In some cases, a meter is required to measure the power
          consumption.  In such a case, this meter Energy Object
          category is meter(2).  If a device is distributing
          electric Energy, the category of the Energy Object is
          distributor (3).  If a device is storing electric Energy,
          the category of the device can be store (4).";
      }

      leaf eoAlternateKey {
        type eman-util:SnmpAdminString;
        config true;
        description
         "The eoAlternateKey object specifies an alternate key
          string that can be used to identify the Energy Object.
          Since Energy Management Systems (EnMS) and Network
          Management Systems (NMSs) may need to correlate objects
          across management systems, this alternate key is provided
          to provide such a link.  This optional value is intended
          as a foreign key or alternate identifier for a
          manufacturer or EnMS/NMS to use to correlate the unique
          Energy Object Id in other systems or namespaces.  If an
          alternate key is not available or is not applicable, then
          the value is the zero-length string.
          The value of eoAlternateKey must remain constant at
          least from one re-initialization of the entity local
          management system to the next re-initialization.";
      }

      leaf eoPowerInterfaceType {
        type enumeration {
          enum inlet  { value 0; }
          enum outlet { value 1; }
          enum both   { value 2; }
        }
        config false;
        description
         "This object describes the Power Interface for an Energy
          Object.  A Power Interface is an interface at which an
          Energy Object is connected to a power transmission
          medium, at which it can in turn receive power, provide
          power, or both.  A Power Interface type can be an inlet(0),
          an outlet(1), or both(2), respectively.";
      }
    }


    /* XXX table comments here XXX */

    list eoRelationEntry {

      key "entPhysicalIndex eoRelationIndex";
      description
       "An entry in this table specifies the Energy relationship
        between Energy objects.  Energy relations between two
        Energy objects are defined in RFC 7326.";
      reference
       " RFC 7326: Energy Management Framework";

      /*** Was originally a keyref. ODL yangtools parser does not support keyref ***/
      leaf entPhysicalIndex {
        type leafref {
          path "/entity:entityPhysical/entity:entPhysicalEntry/entity:entPhysicalIndex";
        }
        config false;
        description
         "Automagically generated keyref leaf.";
      }

      leaf eoRelationIndex {
        type int32 {
          range "0..2147483647";
        }
        config false;
        description
         "This object is an arbitrary index to identify the Energy
          Object related to another Energy Object.";
      }

      leaf eoRelationID {
        type uuid-tc:UUIDorZero;
        config true;
        description
         "This object specifies the Universally Unique Identifier
          (UUID) of the peer (other) Energy Object.  The UUID must
          comply with the specifications of UUID in UUID-TC-MIB.

          If the UUID of the Energy Object is unknown or nonexistent,
          the eoRelationID will be set to a zero-length string
          instead.  It is preferable that the value of
          entPhysicalUUID from ENTITY-MIB is used for values for
          this object.";
        reference
         "RFC 6933: Entity MIB (Version 4)";
      }

      leaf eoRelationship {
        type iana-energytypes:IANAEnergyRelationship;
        config true;
        description
         "This object describes the relations between Energy
          Objects.  For each Energy Object, the relations between
          the other Energy Objects are specified using the bitmap.";
      }

      leaf eoRelationStatus {
        type smiv2:RowStatus;
        config true;
        description
         "The status controls and reflects the creation and
          activation status of a row in this table to specify energy
          relationship between Energy Objects.

          An entry status may not be active(1) unless all objects in
          the entry have the appropriate values.

          No attempt to modify a row columnar object instance value
          in the eoRelationTable should be issued while the value of
          eoRelationStatus is active(1).  The data can be destroyed by
          setting up the eoRelationStatus to destroy(2).";
      }

      leaf eoRelationStorageType {
        type smiv2:StorageType;
        config true;
        description
         "This variable indicates the storage type for this row.";
      }
    }
  }

} /* end of module odl-eman-energyobjectcontext */
