module odl-eman-uuid-tc {

  /*** NAMESPACE / PREFIX DEFINITION ***/
  namespace "urn:opendaylight:params:xml:ns:yang:eman:uuid:tc";
  prefix "uuid-tc";

  /*** LINKAGE (IMPORTS / INCLUDES) ***/

  /*** META INFORMATION ***/
  organization
   "IETF Energy Management Working Group";

  contact
   "WG Email: eman@ietf.org
    Mailing list subscription info:
    http://www.ietf.org/mailman/listinfo/eman

    Dan Romascanu
    Avaya
    Park Atidim, Bldg. #3
    Tel Aviv, 61581
    Israel
    Phone: +972-3-6458414
    Email: dromasca@avaya.com

    Juergen Quittek
    NEC Europe Ltd.
    Network Research Division
    Kurfuersten-Anlage 36
    Heidelberg  69115
    Germany
    Phone: +49 6221 4342-115
    Email: quittek@neclab.eu

    Mouli Chandramouli
    Cisco Systems, Inc.
    Sarjapur Outer Ring Road
    Bangalore 560103
    India
    Phone: +91 80 4429 2409
    Email: moulchan@cisco.com";

  description
   "This MIB module defines TEXTUAL-CONVENTIONs
    representing Universally Unique IDentifiers
    (UUIDs).

    Copyright (c) 2013 IETF Trust and the persons
    identified as authors of the code.  All rights
    reserved.

    Redistribution and use in source and binary forms,
    with or without modification, is permitted
    pursuant to, and subject to the license terms
    contained in, the Simplified BSD License set forth
    in Section 4.c of the IETF Trust's Legal
    Provisions Relating to IETF Documents
    (http://trustee.ietf.org/license-info).";

  revision "2013-04-05" {
    description
     "Initial version of this MIB as published in
      RFC 6933.";
  }

  /*** TYPE DEFINITIONS ***/
  typedef UUID {
    type string {
      length "16";
      pattern "(((([0-9A-Fa-f]{2}){4})(([0-9A-Fa-f]{2}){2})(([0-9A-Fa-f]{2}){2})(([0-9A-Fa-f]{2}){1})(([0-9A-Fa-f]{2}){1})(([0-9A-Fa-f]{2})){15,15})([0-9A-Fa-f]{2}))";
    }
    description
     "Universally Unique Identifier information.  The syntax must
      conform to RFC 4122, Section 4.1.";
  }

  typedef UUIDorZero {
    type string {
      length "0 | 16";
      pattern "((((([0-9A-Fa-f]{2})){0,4294967295})|((([0-9A-Fa-f]{2}){4})(([0-9A-Fa-f]{2}){2})(([0-9A-Fa-f]{2}){2})(([0-9A-Fa-f]{2}){1})(([0-9A-Fa-f]{2}){1})(([0-9A-Fa-f]{2})){15,15})([0-9A-Fa-f]{2}))){0,1}";
    }
    description
     "Universally Unique Identifier information.  The syntax must
      conform to RFC 4122, Section 4.1.

      The semantics of the value zero-length OCTET STRING are
      object-specific and must therefore be defined as part of
      the description of any object that uses this syntax.";
  }

} /* end of module odl-eman-uuid-tc */
